Language="VBSCRIPT"

Sub CATMain()
On Error Resume Next

Dim Elemseleccionado As Selection
    Set Elemseleccionado = CATIA.ActiveDocument.Selection
    If Elemseleccionado.Count2 = 0 Then
      msgbox "NO HAY NADA SELECCIONADO"
    End If

Identificacion_punto = InputBox ("IDENTIFICACION DE LOS PUNTOS ", "Modificar Identificacion de puntos", Identificacion_punto)
I = InputBox ("NUMERO SECUENCA ", "Indices", I)

ind = I

for j = 1 to Elemseleccionado.Count2

if ind < 10 then
   Elemseleccionado.Item(j).Value.Name = Identificacion_punto & "0" & ind
 else
   Elemseleccionado.Item(j).Value.Name = Identificacion_punto & ind
end if

  ind = ind + 1

next


End Sub
